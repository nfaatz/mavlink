package CommonQuantities {
    private import ISQ::*;

    attribute def VelocityComponentValue :> SpeedValue {
        doc
        /* Signed component of a velocity vector along one axis. */
    }
} // package CommonQuantities
